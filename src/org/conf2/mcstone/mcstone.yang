module mcstone {
    namespace "mcstone";
    prefix "mcstone";

    revision 0000-00-00 {
        description "xx";
    }

    grouping position {
        leaf recordTime {
            type int32;
        }
        choice triple {
            case cartesion {
                leaf x {
                    type int32;
                }
                leaf y {
                    type int32;
                }
                leaf z {
                    type int32;
                }
            }
            case polar {
                leaf radius {
                    type int32;
                }
                leaf theta {
                    type int32;
                }
                leaf gamma {
                    type int32;
                }
            }
        }
    }

    /* immutable list of active players */
    list active-players {
        key "name";
        leaf name {
            type string;
        }
    }

    container game {
        list teams {
            max-elements 4;
            key "color";
            leaf color {
                type enumeration {
                    enum red;
                    enum blue;
                    enum green;
                    enum yellow;
                }
            }
            leaf-list members {
                type string;
            }
            leaf spawn-point {
                uses position;
            }
            leaf base-position {
                uses position;
            }
        }
        leaf base-radius {
            type int32;
            config "true";
        }
        list leaderboard {
            container entry {
                /* should be leaf-ref i guess */
                leaf team {
                    type string;
                }
                leaf start-time {
                    type int32;
                }
                leaf duration {
                    type int32;
                }
            }
        }
        leaf time-limit {
            type int32;
        }
        list spawn-inventory {
            container item {
                leaf item {
                    type int32;
                }
                leaf amount {
                    type int32;
                }
            }
        }
        list chest-inventory {
            container item {
                leaf item {
                    type int32;
                }
                leaf amount {
                    type int32;
                }
            }
        }
        list armor {
            leaf item {
                type int32;
            }
        }
    }
}
